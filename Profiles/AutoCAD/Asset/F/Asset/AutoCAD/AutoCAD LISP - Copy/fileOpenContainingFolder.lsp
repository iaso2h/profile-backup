(defun c:fileOpenContainingFolder (/ dwgPath shellCommand) 
  (setq dwgPath (getvar "DWGPREFIX"))

  (if (not (or (null dwgPath) (= dwgPath ""))) 
    (progn 
      (startapp (strcat "explorer " dwgPath))
    )
  )

  ;; Return nil so the command prompt does not show the function name
  (princ)
)(defun c:fileOpenContainingFolder (/ dwgPath shellCommand) 
  (setq dwgPath (getvar "DWGPREFIX"))

  (if (not (or (null dwgPath) (= dwgPath ""))) 
    (progn 
      (startapp (strcat "explorer " dwgPath))
    )
  )

  ;; Return nil so the command prompt does not show the function name
  (princ)
)(defun c:fileOpenContainingFolder (/ dwgPath shellCommand) 
  (setq dwgPath (getvar "DWGPREFIX"))

  (if (not (or (null dwgPath) (= dwgPath ""))) 
    (progn 
      (startapp (strcat "explorer " dwgPath))
    )
  )

  ;; Return nil so the command prompt does not show the function name
  (princ)
)(defun c:fileOpenContainingFolder (/ dwgPath shellCommand) 
  (setq dwgPath (getvar "DWGPREFIX"))

  (if (not (or (null dwgPath) (= dwgPath ""))) 
    (progn 
      (startapp (strcat "explorer " dwgPath))
    )
  )

  ;; Return nil so the command prompt does not show the function name
  (princ)
)
