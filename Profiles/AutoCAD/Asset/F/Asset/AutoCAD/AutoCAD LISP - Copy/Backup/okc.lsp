(defun okc (color / ss1)
  (setq ss1 (ssget))
  (command "._change" ss1 "" "p" "c" color "" )
  (princ)
)    
(setq i 1)
(while (<= i 255)
  (eval (read (strcat "(defun c:" (itoa i) (chr 40)(chr 41) "(okc " (itoa i) "))")))
  (setq i (1+ i))
)
