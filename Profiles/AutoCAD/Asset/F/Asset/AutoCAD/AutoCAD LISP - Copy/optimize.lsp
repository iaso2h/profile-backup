(defun c:optimize (/ cmd) 
  (princ "\n")
  (c:attr2TextAll)
  (c:dimRemoveFontOverride)
  (command "undo" "be")
  (setq cmd (getvar 'cmdecho))
  (setvar 'cmdecho 0)
  (command "-overkill" "All" "" "I" "N" "O" 0.000001 "P" "N" "T" "" "E" "" "A" "" "D")
  (command "undo" "e")
  (setvar 'cmdecho cmd)
  (princ)
)(defun c:optimize (/ cmd) 
  (princ "\n")
  (c:attr2TextAll)
  (c:dimRemoveFontOverride)
  (command "undo" "be")
  (setq cmd (getvar 'cmdecho))
  (setvar 'cmdecho 0)
  (command "-overkill" "All" "" "I" "N" "O" 0.000001 "P" "N" "T" "" "E" "" "A" "" "D")
  (command "undo" "e")
  (setvar 'cmdecho cmd)
  (princ)
)(defun c:optimize (/ cmd) 
  (princ "\n")
  (c:attr2TextAll)
  (c:dimRemoveFontOverride)
  (command "undo" "be")
  (setq cmd (getvar 'cmdecho))
  (setvar 'cmdecho 0)
  (command "-overkill" "All" "" "I" "N" "O" 0.000001 "P" "N" "T" "" "E" "" "A" "" "D")
  (command "undo" "e")
  (setvar 'cmdecho cmd)
  (princ)
)(defun c:optimize (/ cmd) 
  (princ "\n")
  (c:attr2TextAll)
  (c:dimRemoveFontOverride)
  (command "undo" "be")
  (setq cmd (getvar 'cmdecho))
  (setvar 'cmdecho 0)
  (command "-overkill" "All" "" "I" "N" "O" 0.000001 "P" "N" "T" "" "E" "" "A" "" "D")
  (command "undo" "e")
  (setvar 'cmdecho cmd)
  (princ)
)
