;; Quick Block
;; Creates a block instantly out of the objects that you select
;; Reference: http://forums.autodesk.com/t5/Visual-LISP-AutoLISP-and-General/Quick-block/td-p/3454228
;;
(defun c:blockCreateInplace (/ ss i insertPoint savedEntLast ent) 
  (if (not *IsLoadedAttr2Text*) 
    (load "attr2Text.lsp")
  )
  (setq cmd (getvar 'cmdecho))
  (setvar 'cmdecho 0)
  (princ "\n")
  (defun *error* (msg) 
    (if (not (member msg '("Function cancelled" "quit / exit abort" "函数已取消"))) 
      (princ (strcat "Error: " msg "\n"))
    )
    (princ)
  )
  (blockPrompt t t)

  (vl-cmdf "undo" "e")
  (setvar 'cmdecho cmd)

  (princ)
)

(defun blockPrompt (convertAttrChk NestedBlkChk / ss i insertPoint savedEntLast ent) 
  (if 
    (and 
      (setq ss (ssget "_:L"))
      (setq insertPoint (getpoint "请指定插入点：\n"))
    )
    (progn 
      (command "undo" "be")
      (setq savedEntLast (entlast))
      (setq i 0)
      (if (or convertAttrChk NestedBlkChk) 
        (while (< i (sslength ss)) 
          (setq ent (ssname ss i))
          (setq eName (cdr (assoc 0 (entget ent))))
          (cond 
            ((and 
               convertAttrChk
               (eq eName "ATTDEF")
             )
             (ssadd (ssname (attr2TextConvert (ssadd ent (ssadd)) t) 0) ss)
            )
            ((and 
               (null NestedBlkChk)
               (eq eName "INSERT")
             )
             (progn 
               (command "_explode" ent)
               (while (setq ent (entnext savedEntLast)) 
                 (setq savedEntLast ent)
                 (ssadd savedEntLast ss)
               )
             )
            )
          )

          (setq i (1+ i))
        )
      )

      (insertBlock insertPoint ss)
    )
  )
)

(defun insertBlock (insertPoint ss / timeStamp cnt blockName) 
  (setq timeStamp (rtos (getvar "CDATE") 2 6))
  (setq cnt       1
        blockName (strcat timeStamp (itoa cnt))
  )
  (while (tblsearch "BLOCK" blockName) 
    (setq blockName (strcat timeStamp (itoa (setq cnt (1+ cnt)))))
  )
  (command "_.-block" blockName insertPoint ss "")
  (command "_.-insert" blockName insertPoint "" "" "")

  (princ)
)

(defun c:blockCreateInplaceByBlock (/ cmd ss blockColor blockEnt blockObj) 
  (vl-load-com)
  (if (not *IsLoadedAttr2Text*) 
    (load "attr2Text.lsp")
  )
  (princ "\n")
  (defun *error* (msg) 
    (if (not (member msg '("Function cancelled" "quit / exit abort" "函数已取消"))) 
      (princ (strcat "Error: " msg "\n"))
    )
    (princ)
  )
  (setq cmd (getvar 'cmdecho))
  (setvar 'cmdecho 0)

  (blockPrompt t nil)
  (setq blockEnt (entlast))
  (setq blockObj (vlax-ename->vla-object blockEnt))
  (setq blockColor (acad_colordlg 1))
  (if (null blockColor) 
    (setq blockColor 1)
  )
  (vla-put-color blockObj blockColor)
  (vla-put-layer blockObj "0")

  (setq ss (ssadd))
  (ssadd blockEnt ss)
  (if (not *IsLoadedBlockColor*) 
    (load "blockColor.lsp")
  )
  (blockColorSelectionSet ss 0 t)
  (command "undo" "e")
  (setvar 'cmdecho cmd)

  (princ)
)
;; Quick Block
;; Creates a block instantly out of the objects that you select
;; Reference: http://forums.autodesk.com/t5/Visual-LISP-AutoLISP-and-General/Quick-block/td-p/3454228
;;
(defun c:blockCreateInplace (/ ss i insertPoint savedEntLast ent) 
  (if (not *IsLoadedAttr2Text*) 
    (load "attr2Text.lsp")
  )
  (setq cmd (getvar 'cmdecho))
  (setvar 'cmdecho 0)
  (princ "\n")
  (defun *error* (msg) 
    (if (not (member msg '("Function cancelled" "quit / exit abort" "函数已取消"))) 
      (princ (strcat "Error: " msg "\n"))
    )
    (princ)
  )
  (blockPrompt t t)

  (vl-cmdf "undo" "e")
  (setvar 'cmdecho cmd)

  (princ)
)

(defun blockPrompt (convertAttrChk NestedBlkChk / ss i insertPoint savedEntLast ent) 
  (if 
    (and 
      (setq ss (ssget "_:L"))
      (setq insertPoint (getpoint "请指定插入点：\n"))
    )
    (progn 
      (command "undo" "be")
      (setq savedEntLast (entlast))
      (setq i 0)
      (if (or convertAttrChk NestedBlkChk) 
        (while (< i (sslength ss)) 
          (setq ent (ssname ss i))
          (setq eName (cdr (assoc 0 (entget ent))))
          (cond 
            ((and 
               convertAttrChk
               (eq eName "ATTDEF")
             )
             (ssadd (ssname (attr2TextConvert (ssadd ent (ssadd)) t) 0) ss)
            )
            ((and 
               (null NestedBlkChk)
               (eq eName "INSERT")
             )
             (progn 
               (command "_explode" ent)
               (while (setq ent (entnext savedEntLast)) 
                 (setq savedEntLast ent)
                 (ssadd savedEntLast ss)
               )
             )
            )
          )

          (setq i (1+ i))
        )
      )

      (insertBlock insertPoint ss)
    )
  )
)

(defun insertBlock (insertPoint ss / timeStamp cnt blockName) 
  (setq timeStamp (rtos (getvar "CDATE") 2 6))
  (setq cnt       1
        blockName (strcat timeStamp (itoa cnt))
  )
  (while (tblsearch "BLOCK" blockName) 
    (setq blockName (strcat timeStamp (itoa (setq cnt (1+ cnt)))))
  )
  (command "_.-block" blockName insertPoint ss "")
  (command "_.-insert" blockName insertPoint "" "" "")

  (princ)
)

(defun c:blockCreateInplaceByBlock (/ cmd ss blockColor blockEnt blockObj) 
  (vl-load-com)
  (if (not *IsLoadedAttr2Text*) 
    (load "attr2Text.lsp")
  )
  (princ "\n")
  (defun *error* (msg) 
    (if (not (member msg '("Function cancelled" "quit / exit abort" "函数已取消"))) 
      (princ (strcat "Error: " msg "\n"))
    )
    (princ)
  )
  (setq cmd (getvar 'cmdecho))
  (setvar 'cmdecho 0)

  (blockPrompt t nil)
  (setq blockEnt (entlast))
  (setq blockObj (vlax-ename->vla-object blockEnt))
  (setq blockColor (acad_colordlg 1))
  (if (null blockColor) 
    (setq blockColor 1)
  )
  (vla-put-color blockObj blockColor)
  (vla-put-layer blockObj "0")

  (setq ss (ssadd))
  (ssadd blockEnt ss)
  (if (not *IsLoadedBlockColor*) 
    (load "blockColor.lsp")
  )
  (blockColorSelectionSet ss 0 t)
  (command "undo" "e")
  (setvar 'cmdecho cmd)

  (princ)
)
;; Quick Block
;; Creates a block instantly out of the objects that you select
;; Reference: http://forums.autodesk.com/t5/Visual-LISP-AutoLISP-and-General/Quick-block/td-p/3454228
;;
(defun c:blockCreateInplace (/ ss i insertPoint savedEntLast ent) 
  (if (not *IsLoadedAttr2Text*) 
    (load "attr2Text.lsp")
  )
  (setq cmd (getvar 'cmdecho))
  (setvar 'cmdecho 0)
  (princ "\n")
  (defun *error* (msg) 
    (if (not (member msg '("Function cancelled" "quit / exit abort" "函数已取消"))) 
      (princ (strcat "Error: " msg "\n"))
    )
    (princ)
  )
  (blockPrompt t t)

  (vl-cmdf "undo" "e")
  (setvar 'cmdecho cmd)

  (princ)
)

(defun blockPrompt (convertAttrChk NestedBlkChk / ss i insertPoint savedEntLast ent) 
  (if 
    (and 
      (setq ss (ssget "_:L"))
      (setq insertPoint (getpoint "请指定插入点：\n"))
    )
    (progn 
      (command "undo" "be")
      (setq savedEntLast (entlast))
      (setq i 0)
      (if (or convertAttrChk NestedBlkChk) 
        (while (< i (sslength ss)) 
          (setq ent (ssname ss i))
          (setq eName (cdr (assoc 0 (entget ent))))
          (cond 
            ((and 
               convertAttrChk
               (eq eName "ATTDEF")
             )
             (ssadd (ssname (attr2TextConvert (ssadd ent (ssadd)) t) 0) ss)
            )
            ((and 
               (null NestedBlkChk)
               (eq eName "INSERT")
             )
             (progn 
               (command "_explode" ent)
               (while (setq ent (entnext savedEntLast)) 
                 (setq savedEntLast ent)
                 (ssadd savedEntLast ss)
               )
             )
            )
          )

          (setq i (1+ i))
        )
      )

      (insertBlock insertPoint ss)
    )
  )
)

(defun insertBlock (insertPoint ss / timeStamp cnt blockName) 
  (setq timeStamp (rtos (getvar "CDATE") 2 6))
  (setq cnt       1
        blockName (strcat timeStamp (itoa cnt))
  )
  (while (tblsearch "BLOCK" blockName) 
    (setq blockName (strcat timeStamp (itoa (setq cnt (1+ cnt)))))
  )
  (command "_.-block" blockName insertPoint ss "")
  (command "_.-insert" blockName insertPoint "" "" "")

  (princ)
)

(defun c:blockCreateInplaceByBlock (/ cmd ss blockColor blockEnt blockObj) 
  (vl-load-com)
  (if (not *IsLoadedAttr2Text*) 
    (load "attr2Text.lsp")
  )
  (princ "\n")
  (defun *error* (msg) 
    (if (not (member msg '("Function cancelled" "quit / exit abort" "函数已取消"))) 
      (princ (strcat "Error: " msg "\n"))
    )
    (princ)
  )
  (setq cmd (getvar 'cmdecho))
  (setvar 'cmdecho 0)

  (blockPrompt t nil)
  (setq blockEnt (entlast))
  (setq blockObj (vlax-ename->vla-object blockEnt))
  (setq blockColor (acad_colordlg 1))
  (if (null blockColor) 
    (setq blockColor 1)
  )
  (vla-put-color blockObj blockColor)
  (vla-put-layer blockObj "0")

  (setq ss (ssadd))
  (ssadd blockEnt ss)
  (if (not *IsLoadedBlockColor*) 
    (load "blockColor.lsp")
  )
  (blockColorSelectionSet ss 0 t)
  (command "undo" "e")
  (setvar 'cmdecho cmd)

  (princ)
)
;; Quick Block
;; Creates a block instantly out of the objects that you select
;; Reference: http://forums.autodesk.com/t5/Visual-LISP-AutoLISP-and-General/Quick-block/td-p/3454228
;;
(defun c:blockCreateInplace (/ ss i insertPoint savedEntLast ent) 
  (if (not *IsLoadedAttr2Text*) 
    (load "attr2Text.lsp")
  )
  (setq cmd (getvar 'cmdecho))
  (setvar 'cmdecho 0)
  (princ "\n")
  (defun *error* (msg) 
    (if (not (member msg '("Function cancelled" "quit / exit abort" "函数已取消"))) 
      (princ (strcat "Error: " msg "\n"))
    )
    (princ)
  )
  (blockPrompt t t)

  (vl-cmdf "undo" "e")
  (setvar 'cmdecho cmd)

  (princ)
)

(defun blockPrompt (convertAttrChk NestedBlkChk / ss i insertPoint savedEntLast ent) 
  (if 
    (and 
      (setq ss (ssget "_:L"))
      (setq insertPoint (getpoint "请指定插入点：\n"))
    )
    (progn 
      (command "undo" "be")
      (setq savedEntLast (entlast))
      (setq i 0)
      (if (or convertAttrChk NestedBlkChk) 
        (while (< i (sslength ss)) 
          (setq ent (ssname ss i))
          (setq eName (cdr (assoc 0 (entget ent))))
          (cond 
            ((and 
               convertAttrChk
               (eq eName "ATTDEF")
             )
             (ssadd (ssname (attr2TextConvert (ssadd ent (ssadd)) t) 0) ss)
            )
            ((and 
               (null NestedBlkChk)
               (eq eName "INSERT")
             )
             (progn 
               (command "_explode" ent)
               (while (setq ent (entnext savedEntLast)) 
                 (setq savedEntLast ent)
                 (ssadd savedEntLast ss)
               )
             )
            )
          )

          (setq i (1+ i))
        )
      )

      (insertBlock insertPoint ss)
    )
  )
)

(defun insertBlock (insertPoint ss / timeStamp cnt blockName) 
  (setq timeStamp (rtos (getvar "CDATE") 2 6))
  (setq cnt       1
        blockName (strcat timeStamp (itoa cnt))
  )
  (while (tblsearch "BLOCK" blockName) 
    (setq blockName (strcat timeStamp (itoa (setq cnt (1+ cnt)))))
  )
  (command "_.-block" blockName insertPoint ss "")
  (command "_.-insert" blockName insertPoint "" "" "")

  (princ)
)

(defun c:blockCreateInplaceByBlock (/ cmd ss blockColor blockEnt blockObj) 
  (vl-load-com)
  (if (not *IsLoadedAttr2Text*) 
    (load "attr2Text.lsp")
  )
  (princ "\n")
  (defun *error* (msg) 
    (if (not (member msg '("Function cancelled" "quit / exit abort" "函数已取消"))) 
      (princ (strcat "Error: " msg "\n"))
    )
    (princ)
  )
  (setq cmd (getvar 'cmdecho))
  (setvar 'cmdecho 0)

  (blockPrompt t nil)
  (setq blockEnt (entlast))
  (setq blockObj (vlax-ename->vla-object blockEnt))
  (setq blockColor (acad_colordlg 1))
  (if (null blockColor) 
    (setq blockColor 1)
  )
  (vla-put-color blockObj blockColor)
  (vla-put-layer blockObj "0")

  (setq ss (ssadd))
  (ssadd blockEnt ss)
  (if (not *IsLoadedBlockColor*) 
    (load "blockColor.lsp")
  )
  (blockColorSelectionSet ss 0 t)
  (command "undo" "e")
  (setvar 'cmdecho cmd)

  (princ)
)
