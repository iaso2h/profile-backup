;credit: http://bbs.xdcad.net/forum.php?mod=viewthread&tid=726197&highlight=get%2Bunion
(defun getUnion (ents mode / a b c ents1 x) 
  (if (= (type ents) 'PICKSET) (setq ents (xdrx-pickset->ents ents)))
  (setq ents1 ents)
  (while (cdr ents) 
    (setq a (car ents)
          b (cdr ents)
    )
    (setq ents (cdr ents))
    (while (car b) 
      (setq c (car b))
      (if (xdrx-get-union a c) 
        (progn 
          (setq ents (cons a ents)
                b    (vl-remove c b)
                ents (vl-remove c ents)
          )
        )
      )
      (setq b (cdr b))
    )
  )
  (cond 
    ((xdrx-object-iskindof a "region,hatch,mpolygon")
     (if mode (list a) (xdrx-getpropertyvalue a "detach"))
    )
    ((xdrx-object-iskindof a "curve")
     (vl-remove nil (mapcar '(lambda (x) (if (entget x) x)) ents1))
    )
  )
)
