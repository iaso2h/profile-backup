;; http://bbs.mjtd.com/forum.php?mod=viewthread&tid=187150&highlight=%B6%D4%C6%EB
(defun c:spaceOrigin()
	(setq ss(ssget))
	(setvar "cmdecho" 0)
	(command "undo" "be")
	; (initget "e q")
	; (setq f (getkword "\n选择排列方式：[水平(e)/竖直(q)]<e>"))(if (null f)(setq f "e"))
  (setq f "e")
	(setq d 200)
	; (setq d (getdist "\n量取或输入每个对象的间距：<200>"))(if (null d)(setq d 200))
	(setq p '(0  0))
	(setq bz(getvar "osmode"))(setvar "osmode" 0)
	(setq pe (list (+ (car p) d) (cadr p)))
	(setq pee pe)
	(setq pq (list (car p) (- (cadr p) d)))
	(setq pqq pq)
	(repeat (setq n(sslength ss))
		(setq en(ssname ss (setq n (1- n))))
		(setq sss(ssadd en))
		(vla-getboundingbox (vlax-ename->vla-object en) 'minp 'maxp)
		(setq pz (vlax-safearray->list minp))
		(setq py (vlax-safearray->list maxp))
		(setq pzsj(list (car pz) (cadr py)))
		(setq x(- (car py) (car pz)))
		(setq y(- (cadr py) (cadr pz)))
		(setq ee (+ x d))
		(setq qq (+ y d))
		(if (= f "e")
			(progn
				(command "move" sss "" pz pe)
				(setq pe (list (+ (car pe) ee) (cadr pe)))
			)
			(progn
				(command "move" sss "" pzsj pq)
				(setq pq (list (car pq) (- (cadr pq) qq)))
			)
		)
		(if (= f "e")
			(command "move" sss "" pee p)
			(command "move" sss "" pqq p)
		)
	)
	(setvar "osmode" bz)
	(command "undo" "e")
	(setvar "cmdecho" 1)
	(princ)
)
