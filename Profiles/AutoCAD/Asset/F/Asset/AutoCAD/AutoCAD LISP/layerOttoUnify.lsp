(defun changeLayerLineWeight (layerName lineWeight) 
  (if (tblsearch "LAYER" layerName) 
    (command ".-layer" "s" layerName "lw" lineWeight "" "")
  )
)

(defun c:layerOttoUnify (/ layers) 
  (defun *error* (msg) 
    (if (not (member msg '("Function cancelled" "quit / exit abort"))) 
      (princ (strcat "\nError: " msg))
    )
    (princ)
  )
  (setvar "CMDECHO" 0)
  (setvar "NOMUTT" 1)
  (vl-cmdf "undo" "be")

  (setq layers '(("OT-中心线" 0.05)
                 ("OT-标注" 0.09)
                 ("OT-符号" 0.09)
                 ("OT-几何体" 0.15)
                )
  )
  (foreach layerList layers 
    (changeLayerLineWeight (car layerList) (cadr layerList))
  )
  
  (vl-cmdf "undo" "e")
  (setvar "CMDECHO" 1)
  (setvar "NOMUTT" 0)
  (princ)
)
