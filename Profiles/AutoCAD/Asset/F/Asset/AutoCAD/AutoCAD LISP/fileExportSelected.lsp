(defun c:fileExportSelected (/ app docs doc objects ss i n sslist) 
  (setq app (vlax-get-acad-object))
  (setq doc (vla-get-activedocument app))
  (setq docs (vla-get-documents app))
  (setq ss (ssget (list (cons 410 (Getvar "CTAB")))))
  (setq n (sslength ss)
        i 0
  )
  (repeat n 
    (setq sslist (append sslist (list (vlax-ename->vla-object (ssname ss i)))))
    (setq i (1+ i))
  )
  (setq objects (vlax-make-safearray vlax-vbObject (cons 0 (1- n))))
  (vlax-safearray-fill objects sslist)
  (setq doc_new (vla-add docs "c:\\mydwt\\Template\\test.dwt"))
  (vla-copyobjects doc objects (vla-get-modelspace doc_new))
  (princ)
)
