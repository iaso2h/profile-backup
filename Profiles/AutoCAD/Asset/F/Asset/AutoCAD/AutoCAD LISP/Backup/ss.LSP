(defun C:SS ( / s1 i e l f s2)
  (princ "\nSelect source object:")
  (if
    (if
      (setq s1 (ssget "I"))
      (progn (sssetfirst nil nil) s1)
      (setq s1 (ssget))
    )
    (progn
      (repeat (setq i (sslength s1))
        (setq i (1- i)
              e (entget (ssname s1 i))
              l (mapcar '(lambda (a b) (cond ((assoc a e)) (b))) '(0 8 6 62) '(0 0 (6 . "ByLayer") (62 . 256)))
              )
        (if (not (member l f)) (setq f (cons l f)))
        )
      (setq f (mapcar '(lambda (a) (append '((-4 . "<AND")) a '((-4 . "AND>")))) f))
      (setq f (append '((-4 . "<OR")) (apply 'append f) '((-4 . "OR>"))))
      (princ "\n\nSelect area for similar objects...")
      (if (setq s2 (ssget f)) (princ (strcat (itoa (sslength s2)) " objects")))
      (sssetfirst nil s2)
      )
    )
  (if (zerop (getvar 'cmdactive)) (princ) s2)
  )

(defun C:SSL ( / s1 s2 i layer filter)
  (princ "\nSelect source object:")
  (if
    (if
      (setq s1 (ssget "I"))
      (progn (sssetfirst nil nil) s1)
      (setq s1 (ssget))
    )
    (progn
      (repeat (setq i (sslength s1))
        (if
          (not (member (setq layer (strcat (cdr (assoc 8 (entget (ssname s1 (setq i (1- i)))))) ",")) filter))
          (setq filter (cons layer filter))
          )
        )
      (princ "\nSelect area for object on the same layer: ")
      (if
        (setq s2 (ssget (list (cons 8 (apply 'strcat filter)) (assoc 410 (entget (ssname s1 0))))))
        (princ (strcat (itoa (sslength s2)) " objects"))
        )
      (sssetfirst nil s2)
      )
    )
  (if (zerop (getvar 'cmdactive)) (princ) s2)
  )


(defun C:SST ( / s1 obj lst s2 str)
  (princ "\nSelect source object:")
  (if
    (or
      (if
        (setq s1 (cadr (ssgetfirst)))
        (setq str (if
                   (= 1 (sslength s1))
                   (cdr (assoc 1 (entget (ssname s1 0))))
                   (car (sssetfirst nil nil))
                   )
              )
        )
      (if
        (setq s1 (car (entsel)))
        (setq str (cdr (assoc 1 (entget s1))))
        )
      (/= (setq str (getstring t "\nEnter the TEXT to select: ")) "")
      (setq str "*")
      )
    (progn
      (princ "\nSelect the other objects...")
      (sssetfirst nil nil)
      (setq flst (list '(0 . "*TEXT") (cons 1 str)))
      (if
        (setq s2 (ssget (list '(0 . "*TEXT") (cons 1 str))))
        (princ (strcat (itoa (sslength s2)) " objects"))
        )
      (cadr (sssetfirst nil s2))
      )
    )
  (if (zerop (getvar 'cmdactive)) (princ) (cadr (sssetfirst nil s2)))
  )

(defun C:SSD ( / )
  (sssetfirst nil
    (if
      (cadr (ssgetfirst))
      (ssget "I" '((0 . "*dim*")))
      (ssget '((0 . "*dim*"))))
    )
  (princ)
  )

(defun C:SSB ( / s1 i e l f o n s2)
  (princ "\nSelect source object:")
  (if
    (if
      (setq s1 (ssget "I" '((0 . "INSERT"))))
      (progn (sssetfirst nil nil) s1)
      (setq s1 (ssget '((0 . "INSERT"))))
    )
    (progn
      (repeat (setq i (sslength s1))
        (setq i (1- i)
              o (vlax-ename->vla-object (ssname s1 i))
              e (entget (ssname s1 i))
              l (mapcar '(lambda (a b) (cond ((assoc a e)) (b))) '(0 8 6 62) '(0 0 (6 . "ByLayer") (62 . 256)))
              n (cons (vlax-get o (if (vlax-property-available-p o 'EffectiveName) 'EffectiveName 'Name)) n)
              )
        (if (not (member l f)) (setq f (cons l f)))
        )
      (setq f (mapcar '(lambda (a) (append '((-4 . "<AND")) a '((-4 . "AND>")))) f))
      (setq f (append '((-4 . "<OR")) (apply 'append f) '((-4 . "OR>"))))
      (princ "\n\nSelect area for similar blocks...")
      (if (setq s2 (ssget f))
        (repeat (setq i (sslength s2))
          (if
            (not (member (vlax-get (setq o (vlax-ename->vla-object (setq e (ssname s2 (setq i (1- i)))))) (if (vlax-property-available-p o 'EffectiveName) 'EffectiveName 'Name)) n))
            (ssdel e s2)
            )
          )
        )
      (if s2 (princ (strcat (itoa (sslength s2)) " objects")))
      (sssetfirst nil s2)
      )
    )
  (if (zerop (getvar 'cmdactive)) (princ) s2)
  )
;;;(defun C:SSE ( / s1 i e l f s2 p x y s p1 p2)
;;;;;;  (princ "\nSelect source object:")
;;;  (setq p  (getvar 'viewctr)
;;;        y  (/ (getvar 'viewsize) 2.0)
;;;        s  (getvar 'screensize)
;;;        x  (* (car s) (/ y (cadr s)))
;;;        p1 (mapcar '+ p (list x y))
;;;        p2 (mapcar '- p (list x y))
;;;        )
;;;  (if
;;;    (setq s1 (ssget "C" p1 p2))
;;;    (progn
;;;      (repeat (setq i (sslength s1))
;;;        (setq i (1- i)
;;;              e (entget (ssname s1 i))
;;;              l (mapcar '(lambda (a b) (cond ((assoc a e)) (b))) '(0 8 6 62) '(0 0 (6 . "ByLayer") (62 . 256)))
;;;              )
;;;        (if (not (member l f)) (setq f (cons l f)))
;;;        )
;;;      (setq f (mapcar '(lambda (a) (append '((-4 . "<AND")) a '((-4 . "AND>")))) f))
;;;      (setq f (append '((-4 . "<OR")) (apply 'append f) '((-4 . "OR>"))))
;;;;;;      (princ "\nSelect the other objects...")
;;;      (sssetfirst nil nil)
;;;      (if (setq s2 (ssget "X" f)) (princ (strcat (itoa (sslength s2)) " objects")))
;;;      (sssetfirst nil s2)
;;;      )
;;;    )
;;;  (if (zerop (getvar 'cmdactive)) (princ) s2)
;;;  )
